(defun makeline (ptlist)
	(entmake (list
		'(0 . "LINE")
		(cons 8 FLLT_WINDOW)
		(cons 10 (car ptlist))
		(cons 11 (cadr ptlist))
	))
)

(defun in_win (op_ss / l1 l2 pt1 pt2 pt3 pt4 ptm1 ptm2 os oo ent wd /len sc1 sc2)
	(setq 
		l1 (entget (ssname op_ss 0))
		l2 (entget (ssname op_ss 1))
		pt1 (cdr (assoc 10 l1))
		pt2 (cdr (assoc 11 l1))
		len (distance pt1 pt2)
		sc1 (/ (- len 80) (* 2 len))
		sc2 (- 1 sc1)
		ptm1 (append (list (+ (car pt1) (* (- (car pt2) (car pt1))sc1))
							(+ (cadr pt1) (* (- (cadr pt2) (cadr pt1)) sc1))
					)
					(list 0.0)
			) 
		ptm3 (append (list (+ (car pt1) (* (- (car pt2) (car pt1)) sc2))
							(+ (cadr pt1) (* (- (cadr pt2) (cadr pt1)) sc2))
					)
					(list 0.0)
			) 
		pt3 (cdr (assoc 10 l2))
		pt4 (cdr (assoc 11 l2))
		ptm2 (append (list (+ (car pt3) (* (- (car pt4) (car pt3)) sc1))
							(+ (cadr pt3) (* (- (cadr pt4) (cadr pt3)) sc1))
					)
					(list 0.0)
			)
		ptm4 (append (list (+ (car pt3) (* (- (car pt4) (car pt3)) sc2))
							(+ (cadr pt3) (* (- (cadr pt4) (cadr pt3)) sc2))
					)
					(list 0.0)
			)
	)

	(if (inters pt1 pt3 pt2 pt4)
		(mapcar 'makeline (list (list pt1 pt4) (list pt2 pt3) (list ptm1 ptm4) (list ptm3 ptm2)))
		(mapcar 'makeline (list (list pt1 pt3) (list pt2 pt4) (list ptm1 ptm2) (list ptm3 ptm4)))
	)
)

(defun c:win (/ op_ss)
	(prompt "\nSelect frame line to draw:")
	(setq op_ss (ssget (list (cons 8 FLLT_WALL) '(0 . "LINE"))))
	(if (= (sslength op_ss) 2)
		(in_win op_ss)
		(princ "\nSelect error.")
	)
	(princ)
)
