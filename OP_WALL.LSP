; 2025-11-12 rewrite
; 1996-11-08

(defun op_ins (/ wd)
	(if in_door nil (load "door.lsp"))
	(if in_win nil (load "win.lsp"))
	(setq op_wd (if op_wd op_wd "Door"))
	(initget "Window Door")
	(setq wd (getkword (strcat "\nInsert:[Window/Door]. <" op_wd ">:")))
	(setq wd (if wd wd op_wd))
	(setq op_wd wd)
	(cond
		((= wd "Door") (in_door op_ss))
		((= wd "Window") (in_win op_ss))
		(t)
	)
)

(defun op_wall (/ pt1 pt2 ang1 ang01 ang02 pt0 pt3 pt4 ss ent2 dtct_wid insu ufac pt5 pt6 int ang2 wid pt7 pt8 pt9 pt10 pt dis0 grid_wid)
	(setq insu (getvar "insunits"))
	(cond
		((= insu 0)
			(setq ufac 1.0)
		)
		((= insu 4);毫米
			(setq ufac 1.0)
		)
		((= insu 5);厘米
			(setq ufac 0.1)
		)
		((= insu 6);米
			(setq ufac 0.001)
		)
		(t 
			(setq ufac 1.0)
		)
	)
	(setq 
		pt1 (cdr (assoc 10 ent1))
		pt2 (cdr (assoc 11 ent1))
		dtct_wid (* 350.0 ufac)
		grid_wid 50
		ang1 (angle pt1 pt2)
		ang01 (+ ang1 (/ pi 2.0))
		ang02 (- ang1 (/ pi 2.0))
		pt0 (cadr en)
		pt3 (polar pt0 ang01 dtct_wid)
		pt4 (polar pt0 ang02 dtct_wid)
		ss (ssget "f" (list pt3 pt4))
		ss (ssget "p" (list (cons 8 FLLT_WALL) '(0 . "LINE")))
		ss (ssdel (car en) ss)
	)
	(if (= (sslength ss) 1)
		(progn
			; <<< 插入点取整
			(setq 
				pt0 (inters pt3 pt4 pt1 pt2)
				dis0 (fix (/ (distance pt1 pt0) ufac))
				dis0 (* (if (> dis0 grid_wid) (- dis0 (rem dis0 grid_wid)) grid_wid) ufac)
				pt0 (polar pt1 ang1 dis0)
				pt3 (polar pt0 ang01 dtct_wid)
				pt4 (polar pt0 ang02 dtct_wid)
			)
			; 插入点取整 >>>
			(setq op_wid (if op_wid op_wid (* 900.0 ufac)))
			(setq wid (getdist (strcat "\nWidth: <" (rtos op_wid) ">")))
			(setq wid (if wid wid op_wid))
			(setq op_wid wid wid (/ wid 2.0))
			(setq 
				ent2 (entget (ssname ss 0))
				pt5 (cdr (assoc 10 ent2))
				pt6 (cdr (assoc 11 ent2))
				ang2 (angle pt5 pt6)
				int (inters pt3 pt4 pt5 pt6)
				pt0 (inters pt3 pt4 pt1 pt2)
				pt7 (polar pt0 ang1 wid)
				pt8 (polar int ang2 wid)
				pt9 (polar pt0 ang1 (* -1 wid))
				pt10 (polar int ang2 (* -1 wid))
			)
			(entmod (subst (cons 11 pt9) (assoc 11 ent1) ent1))
			(entmod (subst (cons 11 pt10) (assoc 11 ent2) ent2))
			(setvar "clayer" FLLT_WALL)
			(fl_make_line pt7 pt2)
			(fl_make_line pt8 pt6)
			(if (inters pt7 pt8 pt9 pt10)
				(setq pt pt8 pt8 pt10 pt10 pt pt nil)
			)
			(setq op_ss (ssadd))
			(fl_make_line pt7 pt8)
			(setq op_ss (ssadd (entlast) op_ss))
			(fl_make_line pt9 pt10)
			(setq op_ss (ssadd (entlast) op_ss))
		)
	)
)

(defun c:dw (/ ucsf en ln wl ent1 op_ss yn)
	(defun *error* (s_)
		(setvar "cmdecho" 0)
		(fl_undo_end)
		(cmd "_undo" "")
		(setvar "cmdecho" 1)
		(setq *error* *pub_error*)
		(princ (strcat "\n** " s_ " ** "))
		(princ)
	)
	(fl_undo_begin)
	(setvar "cmdecho" 0)
	(setq ucsf (getvar "ucsfollow"))
	(setq clay (getvar "clayer"))
	(setvar "ucsfollow" 0)
	(setvar "expert" 4)
	(cmd "_ucs" "s""$temp$")
	(cmd "_ucs" "w")
	(if (and
			(setq en (entsel "\nPick a wall-line:"))
			(= (setq ln (cdr (assoc 0 (setq ent1 (entget (car en)))))) "LINE")
			(= (setq wl (strcase (cdr (assoc 8 ent1)))) FLLT_WALL)
		)
		(progn 
			(op_wall)
			(if op_ss (op_ins))
		)
		(cond
			((not en) (alert "Nothing picked"))
			((/= ln "LINE") (alert "The selection is NOT Line"))
			((/= wl FLLT_WALL) (alert "The Line is NOT on layer Wall"))
		)
	)

	(setvar "cmdecho" 0)
	(cmd "_ucs" "r" "$temp$")
	(cmd "_ucs" "d" "$temp$")
	(setvar "ucsfollow" ucsf)
	(setvar "clayer" clay)
	(setvar "expert" 0)
	(setvar "cmdecho" 1)
	(fl_undo_end)
	(setq *error* *pub_error*)
	(princ)
)

(princ "loaded. Start as C:DW")
(princ)
