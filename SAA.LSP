; 2025-11-21	Optimization
; 1999-12-03

(defun c:saa (/ olderr sa0 sa1 sa_a k loop)
	(princ "\nChange snap angle in a curtain value. Start as C:SAA.")
	(setq sa0 (getvar "snapang"))
	(setq sa_ang (if sa_ang sa_ang (/ pi 12.0)))
	(setq sa_anp (if sa_anp sa_anp sa0))
	(setq sa_a (/ (* 180 sa_ang) pi))
	(setq loop t)
	(while loop
		(princ "\nSnapang=")
		(princ (rem (/ (* sa0 180) pi) 90))
		(princ "\tPrevious=")
		(princ (rem (/ (* sa_anp 180) pi) 90))
		(initget "Angle 0 Free Previous")
		(setq k (getkword (strcat "\n[Angle/0/Free/Previous]<increase: " sa_a "> ")))
		(cond
			((= k "Angle")
				(setq sa_a1 (getreal "\nAngle: "))
				(setq sa_a (if sa_a1 sa_a1 sa_a))
				(setq sa_ang (/ (* pi sa_a) 180.0))
			)
			((= k "0")
				(setvar "snapang" 0)
				(setq sa_anp sa0)
				(setq loop nil)
			)
			((= k "Free")
				(setq sa_anp sa0)
				(cmd "'snapang")
				(setq loop nil)
			)
			((= k "Previous")
				(setvar "snapang" sa_anp)
				(setq sa_anp sa0)
				(setq loop nil)
			)
			(t
				(setvar "snapang" (rem (+ sa0 sa_ang) pi))
				(setq sa_anp sa0)
				(setq loop nil)
			)
		)
	)
	(princ "\nSnapang: ")
	(princ (rem (/ (* (getvar "snapang") 180) pi) 90))
	(princ)
)

(princ "loaded. Start as C:SAA ")
(princ)
