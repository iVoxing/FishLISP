; :)
; 2025-11-25	opimization

(defun c:cas (/ cl os oo ucsf pwid pt1 pt2 pt3 pt4 pt5 pt6 pt0 pt1_1 pt1_2 pt1_3 pt1_4 ss an1 an2 an3 an4 sq2 sq-2)
	(fl_undo_begin)
	(setq
		cl (getvar "clayer")
		os (getvar "osmode")
		oo (getvar "orthomode")
		ucsf (getvar "ucsfollow")
		pwid (getvar "plinewid")
	)
	(setvar "cmdecho" 0)
	(setvar "osmode" 0)
	(setvar "orthomode" 0)
	(setvar "ucsfollow" 0)

	(cmd "_ucs" "w")
	(setq pt1 (getpoint "\nPick a point: "))
	(if pt1 (setq pt2 (getpoint pt1 "\nPick a point: "))
	(if pt2
		(setq
			an1 (angle pt1 pt2)
			an2 (+ an1 (/ pi 2.0))
			an3 (+ an1 (/ pi 4.0))
			an4 (+ an2 (/ pi 4.0))
			pt3 (polar pt1 an2 600)
			pt4 (polar pt2 an2 600)
			pt0 (list (/ (+ (car pt1) (car pt2)) 2) (/ (+ (cadr pt1) (cadr pt2)) 2))
			sq2 (* 40 (sqrt 2))
			sq-2 (* sq2 -1)
			pt1_1 (polar pt1 an3 sq2)
			pt1_2 (polar pt2 an4 sq2)
			pt1_3 (polar pt3 an4 sq-2)
			pt1_4 (polar pt4 an3 sq-2)
			pt5 (list (/ (+ (car pt1_1) (car pt1_3)) 2) (/ (+ (cadr pt1_1) (cadr pt1_3)) 2))
			pt6 (list (/ (+ (car pt1_2) (car pt1_4)) 2) (/ (+ (cadr pt1_2) (cadr pt1_4)) 2))
		)
	)
	(if (and pt1 pt2 pt3 pt4 pt5 pt6)
		(progn
			(if (tblsearch "layer" FLLT_FUR) (setvar "clayer" FLLT_FUR))
			(setvar "plinewid" 0.0)
			(setq ss (ssadd))
			(fl_make_pline (list pt1 pt2 pt4 pt3) 1)
			(setq ss (ssadd (entlast) ss))
			(fl_make_pline (list pt1_1 pt1_2 pt1_4 pt1_3) 1)
			(setq ss (ssadd (entlast) ss))
			(fl_make_line pt5 pt6)
			(setq ss (ssadd (entlast) ss))
			(setvar "orthomode" 1)
			(command "_rotate" ss "" pt0)
			(setvar "cmdecho" 1)
			(command pause)
			(setvar "cmdecho" 0)
			(cmd "_ucs" "p")
			(setvar "cmdecho" 1)
			(redraw)
		)
	)

	(setvar "clayer" cl)
	(setvar "osmode" os)
	(setvar "orthomode" oo)
	(setvar "ucsfollow" ucsf)
	(setvar "plinewid" pwid)
	(fl_undo_end)
	(princ)
)
