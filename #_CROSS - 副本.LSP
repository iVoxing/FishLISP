;FishLISP
;清除双线交叉

(defun c:xc (/ amt en_lst int int1 int2 ss n m ent1 ent2 en pt1 pt2 pt1-1 pt1-2 pt2-1 pt2-2 amnt num l ent)
	(setvar "cmdecho" 0)
	(fl_undo_begin)
	(setvar "expert" 4)
	(cmd "_.ucs" "s" "xc_temp")
	(prompt "\nSelect X-CROSS lines to edit: ")
	(setq ss (ssget '((0 . "line"))))
	(if ss (setq amt (sslength ss)))
	(setq n 0 en_lst (list))
	(repeat amt
		(setq 
			en (ssname ss n)
			en_lst (append en_lst (list en))
			n (1+ n)
		)
		(redraw en 2)
	)
	(setq n 0 amnt 0)
	(princ "\nNew line: ")
	(setvar "ucsicon" 0)
	(repeat amt
		(setq
			ent1 (entget (nth n en_lst))
			pt1-1 (cdr (assoc 10 ent1))
			pt1-2 (cdr (assoc 11 ent1))
			m (1+ n)
		)
		(if (= m amt) (setq m 0))
		(setvar "ucsfollow" 0)
		(cmd "_.ucs" "e" (cdr (assoc -1 ent1)))
		(setq int_lst (list (car (trans pt1-1 0 1))))
		(repeat (1- amt)
			(setq
				ent2 (entget (nth m en_lst))
				pt2-1 (cdr (assoc 10 ent2))
				pt2-2 (cdr (assoc 11 ent2))
				int (inters pt1-1 pt1-2 pt2-1 pt2-2)
			)
			(if (or (equal int pt1-1) (equal int pt1-2)) (setq int nil))
			(if int (setq int_lst (append int_lst (list (car (trans int 0 1))))))
			(setq m (1+ m))
			(if (= m amt) (setq m 0))
		)
		(setq int_lst (append int_lst (list (car (trans pt1-2 0 1)))))
		(setq int_lst (vl-sort int_lst '<))
		(setq l 0)
		(repeat (/ (length int_lst) 2)
			(setq 
				pt1 (trans (list (nth l int_lst) 0) 1 0)
				pt2 (trans (list (nth (1+ l) int_lst) 0) 1 0)
				ent (subst (cons 10 pt1) (assoc 10 ent1) ent1)
				ent (subst (cons 11 pt2) (assoc 11 ent) ent)
			)
			(entmake ent)
			(setq l (+ l 2))
		)
		(setq n (1+ n))
	)
	(cmd "_.erase" ss "")
	(redraw)
	(cmd "_.ucs" "r" "xc_temp")
	(cmd "_.ucs" "d" "xc_temp")
	(setvar "ucsicon" 1)
	(setvar "expert" 0)
	(fl_undo_end)
	(setvar "cmdecho" 1)
	(princ)
)
