; set my dim style
; just load
; 
; 2025-11-19	rewrite

(foreach itm (list "TXT1.SHX" "HZTXT.SHX")
	(if (findfile itm)
		nil
		(exit (strcat "\n未找到 " itm "，不能正确设置标注字体"))
	)
)

(setvar "expert" 5)
(setvar "cmdecho" 0)
(cmd	"_style"
		"standard"
		"txt1.shx,hztxt.shx"
		"0"		;Height
		"0.8"	;Width factor
		"0"		;Obliquing angle
		"n"		;Backwards?
		"n"		;Upside-down?
		"n"		;Vertical?
)
(setvar "cmdecho"1)

(defun save_dim_style (style_name_)
	(set_base)
	(setvar "cmdecho" 0)
	(cmd "_dimstyle" "save" style_name_)
	(setvar "cmdecho" 1)
)

(defun set_base ()
	(setvar "DIMTOL" 0)
	(setvar "DIMLIM" 0)
	(setvar "DIMTIH" 0)
	(setvar "DIMTOH" 0)
	(setvar "DIMSE1" 0)
	(setvar "DIMSE2" 0)
	(setvar "DIMALT" 0)
	(setvar "DIMTOFL" 1)
	(setvar "DIMTIX" 1)
	(setvar "DIMSOXD" 0)
	(setvar "DIMSD1" 0)
	(setvar "DIMSD2" 0)
	(setvar "DIMUPT" 0)
	(setvar "DIMTOLJ" 1)
	(setvar "DIMALTD" 4)
	(setvar "DIMJUST" 0)
	(setvar "DIMFIT" 5)
	(setvar "DIMTZIN" 0)
	(setvar "DIMALTZ" 0)
	(setvar "DIMALTTZ" 0)
	(setvar "DIMTAD" 1)
	(setvar "DIMUNIT" 2)
	(setvar "DIMALTU" 8)
	(setvar "DIMALTTD" 4)
	(setvar "DIMTXSTY" "STANDARD")
	(setvar "DIMDLI" 10)
	(setvar "DIMEXE" 2)
	(setvar "DIMRND" 0)
	(setvar "DIMDLE" 2)
	(setvar "DIMTP" 0)
	(setvar "DIMTM" 0)
	(setvar "DIMTXT" 3)
	(setvar "DIMCEN" 2)
	(setvar "DIMTSZ" 0)
	(setvar "DIMALTF" 0.0394)
	(setvar "DIMLFAC" 1)
	(setvar "DIMTVP" 0)
	(setvar "DIMTFAC" 1)
	(setvar "DIMPOST" "")
	(setvar "DIMAPOST" "")
	(setvar "DIMCLRE" 0)
	(setvar "DIMCLRD" 0)
	;(setvar "DIMBLK" "")
)

(defun set_arch ()
	(setvar "DIMSAH" 1)
	(setvar "DIMAUNIT" 0)
	(setvar "DIMDEC" 0)
	(setvar "DIMTDEC" 4)
	(setvar "DIMASZ" 1.2)
	(setvar "DIMEXO" 2)
	(setvar "DIMGAP" 1.5)
	(setvar "DIMBLK1" "_archtick")
	(setvar "DIMBLK2" "_archtick")
	(setvar "DIMLDRBLK" "none")
	(setvar "DIMCLRT" 7)
	(save_dim_style "ARCH")
)

(defun set_angular ()
	(setvar "DIMSAH" 0)
	(setvar "DIMAUNIT" 1)
	(setvar "DIMDEC" 2)
	(setvar "DIMTDEC" 2)
	(setvar "DIMASZ" 2)
	(setvar "DIMEXO" 0)
	(setvar "DIMGAP" 1.5)
	(setvar "DIMCLRT" 7)
	(save_dim_style "ARCH$2")
)

(defun set_diameter ()
	(setvar "DIMSAH" 0)
	(setvar "DIMAUNIT" 0)
	(setvar "DIMDEC" 0)
	(setvar "DIMTDEC" 4)
	(setvar "DIMASZ" 2)
	(setvar "DIMEXO" 0)
	(setvar "DIMGAP" 1.5)
	(setvar "DIMCLRT" 7)
	(save_dim_style "ARCH$3")
)

(defun set_radial ()
	(setvar "DIMSAH" 0)
	(setvar "DIMAUNIT" 0)
	(setvar "DIMDEC" 0)
	(setvar "DIMTDEC" 4)
	(setvar "DIMASZ" 2)
	(setvar "DIMEXO" 0)
	(setvar "DIMGAP" 1.5)
	(setvar "DIMCLRT" 7)
	(save_dim_style "ARCH$4")
)

(defun set_leader ()
	(setvar "DIMSAH" 1)
	(setvar "DIMAUNIT" 0)
	(setvar "DIMDEC" 0)
	(setvar "DIMTDEC" 4)
	(setvar "DIMASZ" 0.5)
	(setvar "DIMEXO" 0)
	(setvar "DIMGAP" 1)
	(setvar "DIMBLK1" "_NONE")
	(setvar "DIMBLK2" "_NONE")
	(setvar "DIMCLRT" 7)
	(save_dim_style "ARCH$7")
)

(set_arch)
(set_angular)
(set_diameter)
(set_radial)
(set_leader)

(cmd "_dimstyle" "restore" "ARCH")
(setvar "cmdecho" 1)
(setvar "expert" 0)

(princ "Dimstyle reset to ARCH. ")
(princ)
