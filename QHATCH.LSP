(defun c:qhs (/ ss sc conc_sc stl_sc brk_sc grd_sc ptn)
	(setvar "cmdecho" 0)
	(setvar "cmddia" 0)
	(setq ss (ssget))
	(if ss
		(progn
			(setq 
				sc (getvar "dimscale")
				conc_sc (* 2.5 sc)
				stl_sc (* 20.0 sc)
				brk_sc (* 25.0 sc)
				grd_sc (* 10.0 sc)
			)
			(initget "Brick Conc SConc Grid")
			(setq ptn (getkword "\nPattern: [Brick/Conc/SConc/Grid] "))
			(cond 
				((= ptn "Brick") 	(cmd "_hatch" "ansi31,n" brk_sc "0" ss ""))
				((= ptn "Conc")		(cmd "_hatch" "ar-conc,n" conc_sc "0" ss ""))
				((= ptn "Grid") 	(cmd "_hatch" "ansi37,n" grd_sc "0" ss ""))
				((= ptn "SConc")	(cmd "_hatch" "ar-conc,n" conc_sc "0" ss "" "hatch" "ansi31,n" stl_sc "90" ss ""))
			)
		)
	)
	(setvar "cmdecho" 1)
	(setvar "cmddia" 1)
	(princ)
)

(defun c:qhh (/ olderr ss sc conc_sc stl_sc brk_sc grd_sc ptn)
	(setvar "cmdecho" 0)
	(setvar "cmddia" 0)
	(setq en0 (entlast))
	(princ "\nPick a point: ")
	(command "_bpoly" pause "")
	(setq en (entlast))
	(if (= en en0) nil
		(progn
			(setq 
				sc (getvar "dimscale")
				conc_sc (* 2.5 sc)
				stl_sc (* 20.0 sc)
				brk_sc (* 25.0 sc)
				grd_sc (* 10.0 sc)
			)
			(initget "Brick Conc SConc Grid")
			(setq ptn (getkword "\nPattern: Brick/Conc/SConc/Grid: "))
			(cond
				((= ptn "Brick") (cmd "_hatch" "ansi31,n" brk_sc "0" en ""))
				((= ptn "Conc") (cmd "_hatch" "ar-conc,n" conc_sc "0" en ""))
				((= ptn "Grid") (cmd "_hatch" "ansi37,n" grd_sc "0" en ""))
				((= ptn "SConc")
					(cmd "_hatch" "ar-conc,n" conc_sc "0" en "")
					(cmd "_hatch" "ansi31,n" stl_sc "90" en "")
				)
			)
			(entdel en)
		)
	)
	(setvar "cmdecho" 1)
	(setvar "cmddia" 1)
	(princ)
)

(princ "loaded. Start as C:QHS C:QHH(for R14) ")
(princ)
