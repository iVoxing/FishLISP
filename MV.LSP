(defun c:mkvp (/ os oo pt1 pt2 sc sc1 sc2 pt3 pt4 pt5 cl)
	(setq os (getvar "osmode") oo (getvar "orthomode") cl (getvar "clayer"))
	;(setvar "regenmode" 0)
	(setvar "orthomode" 0)
	(setvar "cmdecho" 0)
	(if (tblsearch "layer" "vp")
		(cmd "_layer" "t" "vp" "u" "vp" "c" "250" "vp" "s" "vp" "")
		(cmd "_layer" "m" "vp" "c" "250" "vp" "")
	)
	(setvar "tilemode" 0)
	(if (= (getvar "cvport") 1)
		nil
		(cmd "_.pspace")
	)
	(setq pt1 (getpoint "\nCorner of vport: "))
	(if pt1 (setq pt2 (getcorner pt1 "\nThe other corner: ")))
	(if pt2
		(progn
		(cmd "_mview" pt1 pt2)
		(cmd "_.mspace")
		(if c:ze (c:ze))
		(setq sc (getint "\nScale of drawing: "))
		(setvar "dimscale" sc)
		)
	)
	(setvar "osmode" 0)
	(if sc
		(setq 
			sc1 (strcat "1/" (rtos sc 2 0))
			sc2 (strcat sc1"xp")
			pt3 (getpoint "\nRegion of drawing: ")
		)
	)
	(if pt3 (setq pt4 (getcorner pt3 "\nThe other corner: ")))
	(if pt4
		(progn
			(setq pt5 (list (/ (+ (car pt3) (car pt4)) 2.0) (/ (+ (cadr pt3) (cadr pt4)) 2.0)))
			(cmd "_zoom" "w" pt3 pt4 "_zoom" "c" pt5 "" "_zoom" sc2)
			(cmd "_.pspace")
		)
	)
	(setvar "regenmode" 1)
	(setvar "clayer" cl)
	(setvar "orthomode" oo)
	(setvar "osmode" os)
	(setvar "cmdecho" 1)
	(princ)
)
