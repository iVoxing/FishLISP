; C:CHSP		Change objects to the other space
; 2025-11-27	optimization

(defun c:chsp (/ ss pt1 MorC ss1)
	(princ "\nChange objects to the other space. Version 2.0 . by Little Fish May 30 1996")
	(setvar "cmdecho" 0)
	(setvar "blipmode" 0)
	(if (= (getvar "tilemode") 1)
		(exit (princ "\nTilemode should be set to 0"))
	)
	(prompt "\nSelect objects to change space:")
	(setq 
		ss (ssget)
		ss1 (ssget "p" '((0 . "VIEWPORT")))
	)
	(if ss1 (cmd "_select" ss "r" ss1 ""))
	(if ss1 (setq ss (ssget "p")))
	(initget "Yes No")
	(setq MorC (getkword "\nDelete old objects <No>: "))
	(setq MorC (if MorC MorC "No"))
	(setq pt1 (getpoint "\nBase point: "))
	(setvar "expert" 2)
	(setvar "regenmode" 0)
	(cmd "_block" "chsptemp" pt1 ss "")
	(if (= MorC "No")
		(cmd "_oops")
	)
	(if (= (getvar "cvport") 1)
		(cmd "_.mspace")
		(cmd "_.pspace")
	)
	(cmd "_insert" "chsptemp" pt1 "" "" "")
	(cmd "_zoom" "e")
	(setq pt1 (cdr (assoc 10 (entget (entlast)))))
	(command "_move" "l" "" pt1)
	(setvar "cmdecho" 1)
	(princ "\n")
	(command pause)
	(setvar "cmdecho" 0)
	(cmd "_explode" "l")
	(setvar "expert" 0)
	(setvar "regenmode" 1)
	(setvar "blipmode" 1)
	(princ)
)
