; Fillet and Dim


(defun c:fnd (/ fr rad earc elarc earcl a1 a2 cen pt ang os)
	(defun *error* (s_)
		(if fr (setvar "filletrad" fr))
		(princ (strcat "** " s_ " **"))
		(setq *error* *pub_error*)
		(princ)
	)
	(if (and fnd_rad (zerop fnd_rad))
		(setq fnd_rad nil)
	)
	(princ "\nFillet radius: ")
	(if fnd_rad
		(progn
			(princ "<")
			(princ fnd_rad)
			(princ "> ")
			(initget 6)
		)
		(initget 7)
	)
	(setq rad (getdist))
	(setq rad (if rad rad fnd_rad))
	(setq fnd_rad rad)
	(setq fr (getvar "filletrad"))
	(setvar "filletrad" rad)
	(command "_Fillet")
	(while (= (getvar "cmdnames") "FILLET")
		(command pause)
	)
	(setq
		earc (entlast)
		elarc (entget earc)
		cen (cdr (assoc 10 elarc))
		a1 (cdr (assoc 50 elarc))
		a2 (cdr (assoc 51 elarc))
		ang (/ (+ a1 a2) 2.0)
		pt (polar cen ang rad)
		earcl (list earc pt)
	)
	(setq os (getvar "osmode"))
	(setvar "osmode" 0)
	(cmd "_dimradius" earcl "")
	(setvar "osmode" os)
	(setvar "filletrad" fr)
	(setq *error* *pub_error*)
	(princ)
)

(princ "loaded. Start as C:FND ")
(princ)
