(defun makeline (xpt1 xpt2)
	(entmake (list '(0 . "LINE") (cons 8 FLLT_WINDOW) (cons 10 xpt1) (cons 11 xpt2)))
)

(defun in_win (op_ss / l1 l2 pt1 pt2 pt3 pt4 ang len0 len1 len2)
	(setq 
		l1 (entget (ssname op_ss 0))
		l2 (entget (ssname op_ss 1))
		pt1 (cdr (assoc 10 l1))
		pt2 (cdr (assoc 11 l1))
		ang (angle pt1 pt2)
		len0 (distance pt1 pt2)
		len1 (/ len0 3)
		len2 (* len1 2)
		pt3 (cdr (assoc 10 l2))
		pt4 (cdr (assoc 11 l2))
		pt3 (if (> (distance pt1 pt3) (distance pt1 pt4)) pt4 pt3)
	)
	(mapcar 'makeline 
		(mapcar '(lambda (x) (polar pt1 ang x)) (list 1 len0 len1 len2))
		(mapcar '(lambda (x) (polar pt3 ang x)) (list 1 len0 len1 len2))
	)
)

(defun c:win (/ op_ss)
	(prompt "\nSelect frame line to draw:")
	(setq op_ss (ssget (list (cons 8 FLLT_WALL) '(0 . "LINE"))))
	(if (= (sslength op_ss) 2)
		(in_win op_ss)
		(princ "\nSelect error.")
	)
	(princ)
)
