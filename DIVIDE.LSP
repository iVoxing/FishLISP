; 2025-11-12 parts request move out from func

(defun dvlin (ent_ parts_ / pt1 pt2 lay ang dis part pt3)
	(setq 
		pt1 (cdr (assoc 10 ent_))
		pt2 (cdr (assoc 11 ent_))
		lay (cdr (assoc 8 ent_))
		ang (angle pt1 pt2)
		dis (distance pt1 pt2)
		dis (/ dis parts_)
		pt3 (polar pt1 ang dis)
	)
	(entmod (subst (cons 11 pt3) (assoc 11 ent_) ent_))
	(repeat (1- parts_)
		(setq pt1 pt3 pt3 (polar pt1 ang dis))
		(entmake (list
			(cons 0 "line")
			(cons 8 lay)
			(cons 10 pt1)
			(cons 11 pt3)
		))
	)
)

(defun dvarc (ent_ parts_ / cen rad lay ang1 ang2 ang)
	(setq 
		cen (cdr (assoc 10 ent_))
		rad (cdr (assoc 40 ent_))
		lay (cdr (assoc 8 ent_))
		ang1 (cdr (assoc 50 ent_))
		ang2 (cdr (assoc 51 ent_))
		ang (/ (- ang2 ang1) parts_)
	)
	(entdel (cdr (assoc -1 ent_)))
	(repeat parts_
		(setq ang2 (+ ang1 ang))
		(entmake (list 
			(cons 0 "ARC")
			(cons 8 lay)
			(cons 10 cen)
			(cons 40 rad)
			(cons 50 ang1)
			(cons 51 ang2)
		))
		(setq ang1 ang2)
	)
)

(defun c:div (/ ent foo parts)
	(while (not ent)
		(setq ent (entsel "\nSelect Line or ARC to edit:"))
	)
	(setq ent (entget (car ent)))
	(cond 
		((= (cdr (assoc 0 ent)) "LINE")
			(setq foo dvlin)
		)
		((= (cdr (assoc 0 ent)) "ARC")
			(setq foo dvarc)
		)
		((and (/= (cdr (assoc 0 ent)) "LINE") (/= (cdr (assoc 0 ent)) "ARC"))
			(exit (princ "\nSelection is NOT Line nor ARC."))
		)
	)
  
	(setq parts (getint "\nHow many parts to divide:"))
	(if (not parts) (exit))
  
	(foo ent parts)
	(princ)
)
