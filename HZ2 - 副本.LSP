(defun c:2shx ()
	(set_style "txt1.shx" "hztxt.shx")
	(princ)
)

(defun set_style(font_new big_new / old_amt new_amt xref_amt next_style style_name font_name big_name font_found big_found ft_set)
	(setvar "cmdecho" 0)
	(setvar "regenmode" 0)
	(setq flag t old_amt 0 new_amt 0 xref_amt 0)
	(while
		(setq 
			next_style (tblnext "style" flag)
			style_name (cdr (assoc 2 next_style))
		)
		(if (= 16 (logand 16 (cdr (assoc 70 next_style))))
			(setq xref_amt (1+ xref_amt))
			(progn
				(setq
					font_name (cdr (assoc 3 next_style))
					big_name (cdr (assoc 4 next_style))
					font_found (or (findfile font_name) (findfile (strcat font_name ".shx")) (findfile (strcat font_name ".ttf")))
					big_found (or (= "" big_name) (findfile big_name) (findfile (strcat big_name ".shx")) (findfile (strcat big_name ".ttf")))
					font_name (if font_found font_name font_new)
					big_name (if big_found big_name big_new)
					ft_set (strcat font_name "," big_name)
					ft_set (if (= ft_set (strcat font_new ",")) (strcat font_new "," big_new) ft_set)
				)
				(if (and font_found big_found)
					(setq old_amt (1+ old_amt))
					(setq new_amt (1+ new_amt))
				)
				(cmd "_style" style_name ft_set "0" "" "0")
				(while (= "STYLE" (getvar "cmdnames"))
					(cmd "_n")
				)
			)
		)
		(setq flag nil)
	)
	(setvar "regenmode" 1)
	(cmd "_regen")
	(setvar "cmdecho" 1)
	(princ "\n")
	(princ (strcat (rtos old_amt 2 0) " 字体风格保留。"))
	(princ (strcat (rtos new_amt 2 0) " 字体风格修改。"))
	(if (zerop xref_amt) nil (princ (strcat (rtos xref_amt 2 0) " 外部引用字体风格忽略。")))
)

(princ "loaded. Start as C:2SHX")
(princ)
