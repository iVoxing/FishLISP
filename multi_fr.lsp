; FishLISP
; Multiple fillet
; 2020-11-18 v1.0

(defun c:mfr (/ loop k old_rad new_rad line_ss point_list join_list n line_ent c pt ss)
	(setq loop 1)
	(while loop
		(setq old_rad (getvar "filletrad"))
		(initget "Radius Select")
		(setq
			k (getkword (strcat "\n[Radius: " (rtos old_rad 2 2) "]<Select #-CROSS lines>: "))
			k (if k k "Select")
		)
		(if (= k "Radius")
			(progn
				(setq new_rad (getreal (strcat "\nRadius: <" (rtos old_rad 2 2) ">")))
				(setq new_rad (if new_rad new_rad old_rad))
				(setvar "filletrad" new_rad)
			)
			(setq loop nil)
		)
	)
	(setq line_ss (ssget '((0 . "LINE"))))
	(if line_ss
		(progn
			(setq
				point_list	(list)
				join_list	(list)
				n 0
			)
			(repeat (sslength line_ss)
				(setq line_ent (entget (ssname line_ss n)))
				(foreach c '(10 11)
					(setq pt (cdr (assoc c line_ent)))
					(if (member pt point_list)
						(setq join_list (append join_list (list pt)))
						(setq point_list (append point_list (list pt)))
					)
				)
				(setq n (1+ n))
			)
			(if join_list
				(mapcar
					'(lambda (pt_ / ss)
						(setq ss (ssget "x" (list '(-4 . "<OR")
							'(-4 . "<AND") '(0 . "LINE") (cons 10 pt_) '(-4 . "AND>")
							'(-4 . "<AND") '(0 . "LINE") (cons 11 pt_) '(-4 . "AND>")
						'(-4 . "OR>"))))
						(cmd "_.fillet" (ssname ss 0) (ssname ss 1))
					)
					join_list
				)
				(princ "\nNo joioner found.")
			)
		)
		(princ "\nNo line Selected.")
	)
	(princ)
)

(princ "\nFishLISP C:MFR ")
(princ)
