(defun c:tar (/ pt1 pt2 pt3 len oplw os)
	(setq
		oplw (getvar "plinewid")
		os (getvar "osmode")
	)
	(setvar "osmode" 0)
	(setvar "cmdecho" 0)
	(if (and (setq pt1 (getpoint "\n箭头起点: ")) (setq pt2 (getpoint pt1 "箭头终点: ")))
		(progn
			(setq len (distance pt1 pt2))
			(command "_.pline" pt1 "w" 0 (* 1.8 len) pt2)
			(command "_w" (* 0.4 len) (* 1.3 len) "a")
			(princ "\n箭头尾部: ")
			(command pause)
			(if (= (getvar "cmdnames") "PLINE")
				(command "")
				(entdel (entlast))
			)
		)
	)
	(setvar "plinewid" oplw)
	(setvar "osmode" os)
	(setvar "cmdecho" 1)
	(princ)
)
