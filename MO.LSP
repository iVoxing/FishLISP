(defun c:mo (/ olderr os dist dis dis0 ens pt ent pt1 amt)
	(prompt "\nMultiple Offset, FishLISP, May 13 1996")
	(setq os (getvar "osmode"))
	(setvar "osmode" 0)
	(setq dist (getvar "offsetdist"))
	(setq dis (getdist (strcat "\nOffset distance <" (rtos (if (minusp dist) 0.0 dist)) ">:"))
	(if (= dis nil) (setq dis dist))
	(setq dis0 dis)
	(setq amt (getint "\nHow many time to offset, or RETURN to apply a distance:"))
	(if amt nil
		(setq amt (fix (/ (getdist "\nFirst point:") dis0)))
	)
	(while (setq ens (entsel))
		(setq 
			pt (cadr ens)
			ent (car ens)
			pt1 (getpoint "\nWhich side :")
		)
		(repeat amt 
			(cmd "_offset" dis pt pt1 "")
			(setq dis (+ dis dis0))
		)
		(setq dis dis0)
	)
	(setvar "offsetdist" dis0)
	(setvar "osmode" os)
	(setvar "cmdecho" 1)
	(princ)
)
