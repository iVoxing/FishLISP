(defun c:2shx ()
	(set_style "txt1.shx,hztxt.shx" "0.8")
	(princ)
)

(defun c:2ttf ()
	(set_style "sursong.ttf" "1")
	(princ)
)

(defun set_style (font_set_ wid_fac_ / ft_set next_style style_name flag st_name)
	(setvar "cmdecho" 0)
	(setvar "regenmode" 0)
	(princ (strcat "\nSpecify full font name or font filename (TTF or SHX) <" font_set_ ">: "))
	(setq ft_set (getstring 1))
	(if (= "" ft_set)
		(setq ft_set font_set_)
	)
	(setq flag t amnt 0)
	(while
		(setq next_style (tblnext "style" flag))
		(setq style_name (cdr (assoc 2 next_style)))
		(setq flag nil)
		(cmd "_style" style_name ft_set "0" wid_fac_ "0")
		(while (= "STYLE" (getvar "cmdnames"))
			(cmd "_n")
		)
		(setq amnt (1+ amnt))
	)
	(setvar "regenmode" 1)
	(cmd "_regen")
	(setvar "cmdecho" 1)
	(princ (strcat "\n" (rtos amnt 2 0) " Style changed to '" (strcase ft_set) "'."))
)

(princ)
