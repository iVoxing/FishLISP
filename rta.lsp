(defun c:rta (/ ang pt ss p0 en)
	(setq RTA:ANG (if RTA:ANG RTA:ANG 0))
	(setq ang (getangle (strcat "\nAngle: <" RTA:ANG "> ")))
	(setq ang (if ang (/ (* 180 ang) pi)))
	(setq ang (if ang ang RTA:ANG))
	(setq RTA:ANG ang)
	(setq ang (- ang))
	(initget "Object")
	(while (setq pt (getpoint "\nSpecify base point[Object base]: "))
		(cond
			((= pt "Object")
				(setq ss (ssget) idx 0)
				(repeat (sslength ss)
				(setq 
					en (ssname ss idx)
					p0 (cdr (assoc 10 (entget en)))
				)
				(setvar "cmdecho" 0)
				(if ss (cmd "_rotate" en "" p0 ang))
					(setvar "cmdecho" 1)
					(setq idx (1+ idx))
				)
			)
			((listp pt)
				(setq ss (ssget))
				(setvar "cmdecho" 0)
				(if ss (cmd "_rotate" ss "" pt ang))
				(setvar "cmdecho" 1)
			)
		)
		(initget "Object")
	)
	(princ)
)

(princ "loaded. C:RTA ")
(princ)
