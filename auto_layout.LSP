(defun c:atlo ()
    (setvar "cmdecho" 0)
    (cmd "_layout" "s" "")
    (cmd "_layout" "t" "./A3_title_1.dwg" "A3")
    (cmd "_layout" "d" (getvar "ctab"))
    (cmd "_zoom" "e")
    (cmd "_mspace" "zoom" "e")
    (c:scset)
    (cmd "_pspace" "zoom" "e")
    (cmd "_layout" "r" (getvar "ctab") "A3")
    (setvar "cmdecho" 1)
    (princ)
)
(princ "loaded. C:atlo")
(princ)
