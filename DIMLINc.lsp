; 2000-06-05调用新的Sort函数；
; 增加错误自陷；
; 改进界面。
;

(setq olderr *error*)
(defun *error* (s)
	(setq *error* olderr olderr nil)
	(princ "加载失败！ \n搜索路径中找不到所必需的FUNCTION.LSP。")
	(princ)
)

(if (findfile "function.lsp")
	(load "function")
	(exit (princ "\n Function module not found. "))
)

(setq *error* olderr olderr nil)

(defun c:dl (/ ss amnt pt_base pt_ext olderr)
	(cssave)
	(prompt "\n选取要标注的LINE：")
	(setq ss (ssget '((0 . "LINE"))))
	(if ss (setq amnt (sslength ss)))
	(if (> amnt 1)
		(setq pt_base (getpoint "\n标注基线位置："))
	)
	(if pt_base (setq pt_ext (getpoint pt_base "\n标注延长线位置：<@>")))
	(setq pt_ext (if pt_ext pt_ext pt_base))
	(fl_bench_begin)
	(if pt_ext (dimlin))
	(csrestore)
	(setq *error* olderr olderr nil)
	(fl_bench_end)
	(princ)
)

(defun dimlin ()
	(setq 
		oo (getvar "orthomode")
		os (getvar "osmode")
		cl (getvar "clayer")
		ucsf (getvar "ucsfollow")
	)
	(setvar "cmdecho" 0)
	(setvar "blipmode" 0)
	(setvar "orthomode" 0)
	(setvar "osmode" 0)
	(setvar "ucsfollow" 0)
	(setvar "ucsicon" 0)
	(cmd "_layer" "m" FLLT_DIM0 "c" "g" "" "")
	(setq 
		ent (entget (ssname ss 0))
		pt1 (cdr (assoc 10 ent))
		pt2 (cdr (assoc 11 ent))
	)
	(cmd "_ucs" "z" pt1 pt2)
	(setq 
		y_list (list)
		pt_ext (trans pt_ext 0 1)
		pt_base (trans pt_base 0 1)
		x0 (car pt_ext)
		idx 0
	)
	(repeat amnt
		(setq y_list (append y_list (list (cadr (trans (cdr (assoc 10 (entget (ssname ss idx)))) 0 1)))))
		(setq idx (1+ idx))
	)
	(setq y_list (vl-sort y_list '<))
	(mapcar 
		'(lambda (y1_ y2_)
			(cmd "_dim1" "ver" (list x0 y1_) (list x0 y2_) pt_base "")
		)
		y_list
		(cdr y_list)
	)
	(setvar "cmdecho" 1)
	(setvar "orthomode" oo)
	(setvar "osmode" os)
	(setvar "clayer" cl)
	(setvar "blipmode" 1)
	(setvar "ucsfollow" ucsf)
	(setvar "ucsicon" 1)
)

(princ "\n加载成功。用命令DIMLIN运行。")
(princ)
