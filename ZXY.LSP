(if (tblsearch "layer" FLLT_AXIS) nil (load "reini"))

(defun C:RENUM (/ os cl ss ssl sc n en_ins en_att old_attr new_attr axi_num_layer attr)
	(setq 
		os (getvar "osmode")
		sc (getvar "dimscale")
		cl (getvar "clayer")
		attr (getvar "attreq")
	)
	(setvar "attreq" 1)
	(setvar "CMDECHO" 0)
	(setvar "BLIPMODE" 0)
	(setvar "osmode" 0)
	(setq ss (ssget '((0 . "INSERT") (2 . "axi*"))))
	(if ss 
		(setq ssl (sslength ss) n 0)
		(setq ssl 0)
	)
	(setvar "clayer" FLLT_AXIS)
	(repeat ssl 
		(setq
			en_ins (ssname ss n)
			en_ins_pt (cdr (assoc 10 (entget en_ins)))
			old_attr (cdr (assoc 1 (entget (entnext en_ins))))
			new_attr (strcase (getstring (strcat "\nNew Nummber: <" old_attr ">")))
			new_attr (if (= new_attr "") old_attr new_attr)
		)
		(entdel en_ins)
		(if (> (strlen new_attr) 1)
			(cmd "_insert" "axi" (trans en_ins_pt 0 1) sc "" 0 new_attr)
			(cmd "_insert" "axi0" (trans en_ins_pt 0 1) sc "" 0 new_attr)
		)
		(setq n (1+ n))
	)
	(setvar "clayer" cl)
	(setvar "CMDECHO" 1)
	(setvar "BLIPMODE" 1)
	(setvar "osmode" os)
	(setvar "attreq" attr)
	(princ)
)

(defun C:INSNUM (/ olderr os cl sc sp ep old_attr ins ang attr)
	(setq 
		os (getvar "osmode")
		sc (getvar "dimscale")
		cl (getvar "clayer")
		attr (getvar "attreq")
	)
	(setvar "attreq" 1)
	(setvar "CMDECHO" 0)
	(setvar "BLIPMODE" 0)
	(setvar "clayer" FLLT_AXIS)
	(setq loop t)
	(while loop 
		(setvar "osmode" 167)
		(setq sp (getpoint "\nStart Point: "))
		(if sp (setq ep (getpoint sp "\nEnd Point: ")) (setq loop nil))
		(if ep (setq old_attr (getstring "\nNummber: ")) (setq loop nil))
		(if old_attr 
			(progn 
				(setq 
					old_attr (strcase old_attr)
					ins(polar ep (setq ang (angle sp ep)) (* sc 4))
				)
				(if (> (strlen old_attr) 1)
					(progn 
						(cmd "_line" sp ep "")
						(setvar "osmode" 0)
						(cmd "_insert" "axi" ins sc "" 0 old_attr)
					)
					(progn 
						(cmd "_line" sp ep "")
						(setvar "osmode" 0)
						(cmd "_insert" "axi0" ins sc "" 0 old_attr)
					)
				)
			)
			(setq loop nil)
		)
	)
	(setvar "clayer" cl)
	(setvar "CMDECHO" 1)
	(setvar "osmode" os)
	(setvar "attreq" attr)
	(princ)
)

(defun C:INSAXIS (/ cl sp ep)
	(setvar "cmdecho" 0)
	(setvar "blipmode" 0)
	(setq cl (getvar "clayer"))
	(cmd "_layer" "m" FLLT_AXIS "c" "1" FLLT_AXIS "lt" "acad_iso04w100" FLLT_AXIS "")
	(setq 
		sp (getpoint "\nStart point:")
		ep (getpoint sp "\nEnd point:")
	)
	(cmd "_line" sp ep "")
	(setvar "clayer" cl)
	(setvar "blipmode" 1)
	(setvar "cmdecho" 1)
	(princ)
)

(princ "loaded. Start as C:INSNUM C:RENUM C:INSAXIS ")
(princ)
