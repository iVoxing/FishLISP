(defun c:wchk (/ a b c d ss)
	(setvar "cmdecho" 0)
	(setq 
		a (ssget "x" '((0 . "LINE") (8 . "wall,door,window")))
		b (ssget "x" '((8 . "wall,door,window")(-3 ("FL_WALL"))))
		c (ssget "x" '((0 . "LINE") (8 . "wall-base")))
	)
	(cmd "_select" a c "r" b "")
	(grclear)
	(cmd "_select" "p" "")
	(setq ss (ssget "p"))
	(setq d (sslength c))
	(setq d (if d d 0))
	(princ "\n")
	(if ss
		(princ (- (sslength ss) d))
		(princ "0")
	)
	(princ " unregistered Wall-line found. ")
	(setvar "cmdecho" 1)
	(princ)
)

(defun wup (en_ / ent xdt ss rpt idx)
	(setq ent (entget en_ '("FL_WALL")))
	(if ent (setq xdt (cadr (assoc -3 ent))))
	(if xdt
		(setq 
			ss (ssget (list '(0 . "LINE") (cons 8 FLLT_WALL)))
			xdt (list -3 (subst '(1000 . "Wall_line") (nth 3 xdt) xdt))
		)
	)
	(if ss (setq rpt (sslength ss) idx 0) (setq rpt 0))
	(repeat rpt
		(entmod (append (entget (ssname ss idx)) (list xdt)))
		(setq idx (1+ idx))
	)
)

(defun c:wup ()
	(setvar "cmdecho" 0)
	(cmd "_zoom" "1x")
	(setvar "cmdecho" 1)
	(setq wb_en (entsel "\nSelect a Wall-base line: "))
	(if wb_en (wup (car wb_en)))
	(princ)
)

(defun c:swl (/ en ent xdt pt1 pt2)
	(setvar "cmdecho" 0)
	(cmd "_zoom" "1x")
	(setvar "cmdecho" 1)
	(setq en (entsel "\nSelect a Wall-base line: "))
	(if en (setq ent (entget (car en) '("FL_WALL"))))
	(if ent (setq xdt (cadr (assoc -3 ent))))
	(if xdt
		(progn
			(setvar "clayer" FLLT_WALL)
			(setq xdt (list -3 (subst '(1000 . "Wall_line") (nth 3 xdt) xdt)))
			(while (setq pt1 (getpoint "\nFrom point: "))
				(if pt1 (setq pt2 (getpoint pt1 "\nTo point: ")))
				(entmake (list '(0 . "LINE") (cons 8 FLLT_WALL) (cons 10 pt1) (cons 11 pt2) xdt))
			)
		)
	)
	(princ)
)

(defun c:swb (/ pt1 pt2 dist wb_xdt xdt ent)
	(setvar "cmdecho" 0)
	(cmd "_zoom" "1x")
	(setvar "cmdecho" 1)
	(setq pt1 (getpoint "\nFrom point: "))
	(if pt1 (setq pt2 (getpoint pt1 "\nTo point: ")))
	(if pt2 (setq dist (getint "\nWall width: ")))
	(if dist
		(progn
			(setq ent (entmake (list '(0 . "LINE") '(8 . "wall-base") (cons 10 pt1) (cons 11 pt2))))
			(setq wb_xdt (list -3 (list (strcat "FISH_WALL_" (cdr (assoc 5 (entget (entlast)))))
										(cons 1000 "Wall_base")
										(cons 1002 "{")
										(cons 1041 dist)
										(cons 1002 "}")
									)
						)
			)
			(entmod (append ent (list wb_xdt)))
			(wup (entlast))
		)
	)
	(princ)
)

(princ "loaded. Start as C:WCHK C:WUP C:SWL")
(princ)
