(defun c:dwgn (/ str pt h)
	(setvar "cmdecho" 0)
	(setq str (strcat (getvar "dwgprefix") (getvar "dwgname")))
	(if (setq pt (getpoint "\nInsert point: "))
		(if (setq h (getreal "\nText height: "))
			(if (= (getvar "cvport") 1)
				(entmake (list '(0 . "TEXT") (cons 1 str) (cons 10 pt) (cons 40 h) '(67 . 1)))
				(entmake (list '(0 . "TEXT") (cons 1 str) (cons 10 pt) (cons 40 h) '(67 . 0)))
			)
		)
	)
	(princ)
)

(princ "loaded. Start as C:DWGN ")
(princ)
