(defun c:vv (/ flg loop pt0 pt1 pt2 pt3 pt4 vnm spc hei wid k)
	(setvar "cmdecho" 0)
	(setq flg t loop t)
	(while (and loop (setq vw (tblnext "view" flg)))
		(if flg
			(if c:ze
				(c:ze)
				(cmd "_zoom" "e")
			)
		)
		(setq 
			pt0 (cdr (assoc 10 vw))
			vnm (cdr (assoc 2 vw))
			spc (cdr (assoc 70 vw))
			hei (/ (cdr (assoc 40 vw)) 2.0)
			wid (/ (cdr (assoc 41 vw)) 2.0)
			pt1 (polar (polar pt0 (/ pi -2) hei) pi wid)
			pt2 (polar (polar pt0 (/ pi -2) hei) 0 wid)
			pt3 (polar (polar pt0 (/ pi 2) hei) 0 wid)
			pt4 (polar (polar pt0 (/ pi 2) hei) pi wid)
		)
		(grvecs (list 1 pt1 pt2 1 pt2 pt3 1 pt3 pt4 1 pt4 pt1))
		(princ (strcat "\nView name: " vnm))
		(initget "Next Restor Delete renaMe eXit")
		(setq k (getkword "\n[Restor/Delete/renaMe/eXit]<Next view>: "))
		(setq k (if k k "Next"))
		(cond
			((= k "Next") (redraw))
			((= k "Restor")
				(cmd "_view" "r" vnm)
				(setq loop nil)
			)
			((= k "Delete")
				(cmd "_view" "d" vnm)
				(redraw)
			)
			((= k "renaMe")
				(setq nnm (getstring (strcat "\nEnter new view name: <" vnm ">")))
				(if (= nnm "") (setq nnm vnm))
				(if (= nnm vnm) nil (cmd "_rename" "vi" vnm nnm))
				(redraw)
			)
			((= k "eXit")
				(setq loop nil)
				(redraw)
			)
		)
		(setq flg nil)
	)
	(setvar "cmdecho" 1)
	(princ)
)

(princ "loaded. Start as C:VV ")
(princ)
