(defun c:scel (/ dims el_ss el_amt idx el_ent osm ins_pt ins_sc)
	(prompt "\nFishLISP. 5-28-1998. ")
	(prompt "\nRescale elevation blocks. ")
	(initget 6)
	(setq dims (getreal (strcat "\nDimscale: <" (rtos (getvar "dimscale")) "> ")))
	(setq dims (if dims dims (getvar "dimscale")))
	(setq el_ss (ssget '((0 . "INSERT")(2 . "EL??,EL??,SY1,SY2,SY3,SY4,DIM_BG,DIM_RL,ZBR,ZBL,AL,AR"))))
	(setq 
		el_amt (if el_ss (sslength el_ss) 0)
		idx 0
		osm (getvar "osmode")
	)
	(cssave)
	(setvar "cmdecho" 0)
	(setvar "osmode" 0)
	(repeat el_amt
		(setq 
			el_en (ssname el_ss idx)
			el_ent (entget el_en)
			ins_pt (cdr (assoc 10 el_ent))
			ins_sc (abs (cdr (assoc 41 el_ent)))
		)
		(if (= ins_sc dims) nil (cmd "_scale" el_en "" ins_pt "r" ins_sc dims))
		(setq idx (1+ idx))
	)
	(csrestore)
	(redraw)
	(setvar "osmode" osm)
	(setvar "cmdecho" 1)
	(princ)
)

(princ "loaded. Start as C:SCEL. ")
(princ)
