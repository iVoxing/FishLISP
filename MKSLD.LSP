(defun c:mksld (/ dwg_list dwg_name)
	(prompt "\nFishLISP. 12/25/1997. ")
	(prompt "\nBatch make slides. v1.0. ")
	(setq list_file (getstring "Enter the Drawing-File-List file name: "))
	(if (findfile list_file)
		(progn
			(setvar "cmdecho" 0)
			(setq dwg_list (open list_file "r"))
			(while (setq dwg_name (read-line dwg_list))
				(cmd "_insert" dwg_name "0,0" "" "" "")
				(cmd "_zoom" "E")
				(cmd "_zoom" "0.95x")
				(cmd "_mslide" (getvar "insname"))
				(entdel (entlast))
			)
			(close dwg_list)
			(setvar "cmdecho" 1)
		)
		(princ "\nFile not found! ")
	)
	(princ)
)
