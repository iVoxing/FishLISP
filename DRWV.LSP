; 用 pline 或 vectors 画出已保存的 views

(defun c:drwv (/ os pw flg loop pt0 pt1 pt2 pt3 pt4 vnm spc hei wid k)
	(setvar "cmdecho" 0)
	(setq os (getvar "osmode"))
	(setq pw (getvar "plinewid"))
	(setvar "osmode" 0)
	(setvar "plinewid" 0.0)
	
	(setq drwv_k (if drwv_k drwv_k "Pline"))
	(initget "Pline Vector")
	(setq k (getkword (strcat "\nDraw in [Pline/Vector]: <" drwv_k "> ")))
	(setq k (if k k drwv_k))
	(setq drwv_k k)

	(setq flg t loop t)
	(while (and loop (setq vw (tblnext "view" flg)))
		(setq 
			pt0 (cdr (assoc 10 vw))
			;pt0 (trans pt0 1 0)
			vnm (cdr (assoc 2 vw))
			spc (cdr (assoc 70 vw))
			ang 0;(- 0 (cdr (assoc 50 vw)))
			hei (/ (cdr (assoc 40 vw)) 2.0)
			wid (/ (cdr (assoc 41 vw)) 2.0)
			pt1 (polar (polar pt0 (+ (/ pi -2) ang) hei) (+ pi ang) wid)
			pt2 (polar (polar pt0 (+ (/ pi -2) ang) hei) (+ 0 ang) wid)
			pt3 (polar (polar pt0 (+ (/ pi 2) ang) hei) (+ 0 ang) wid)
			pt4 (polar (polar pt0 (+ (/ pi 2) ang) hei) (+ pi ang) wid)
		)
		(if (= k "Vector")
			(grvecs (list 1 pt1 pt2 1 pt2 pt3 1 pt3 pt4 1 pt4 pt1 1 pt1 pt3 1 pt2 pt4))
			(cmd "_pline" pt1 pt2 pt3 pt4 "c")
		)
		(setq flg nil)
	)
	(setvar "osmode" os)
	(setvar "plinewid" pw)
	(setvar "cmdecho" 1)
	(princ)
)

(princ "loaded. Start as C:DRWV ")
(princ)
