; 2005-04-15 v1.1
; 1998-01-21 v1.0	This application is based on the system varibale CMDNAMES.

(defun wrt (/ dim pt pre)
	(princ "test")
	(setq txt_layer FLLT_AREA)
	(setq insu (getvar "insunits"))
	(setq wa_pre (if wa_pre wa_pre 3))
	(setq wa_psf (if wa_psf wa_psf "m%%199"))
	(if (and wa_ufa wa_dfa)
		nil
		(cond
			((= insu 0)
				(setq wa_ufa 1000000.0)
				(setq wa_dfa 1.0)
			)
			((= insu 4)
				(setq wa_ufa 1000000.0)
				(setq wa_dfa 1.0)
			)
			((= insu 5)
				(setq wa_ufa 10000.0)
				(setq wa_dfa 0.1)
			)
			((= insu 6)
				(setq wa_ufa 1.0)
				(setq wa_dfa 0.001)
			)
			(t
				(setq wa_ufa 1.0)
				(setq wa_dfa 0.001)
			)
		)
	)
	(princ "\nDimscale: ")
	(princ (getvar "dimscale"))
	(princ "\t Units: ")
	(princ (nth (getvar "insunits") (list "No units" "Inches" "Feet" "Miles" "Millimeters" "Centimeters" "Meters" "Kilometers" "Microinches" "Mils" "Yards" "Angstroms" "Nanometers" "Microns" "Decimeters" "Dekameters" "Hectometers" "Gigameters" "Astronomical Units" "Light Years" "Parsecs")))
	(princ "\t Precision: ")
	(princ wa_pre)
	(princ "\t PostFix: ")
	(princ wa_psf)
	(initget "Dimscale Precision Units postFix")
	(setq pt (getpoint "\n[Dimscale/Units/Precision/postFix]<Pick a point to write the area value>: "))
	(cond
		((not pt)
			(princ (strcat "\nArea of this region is " (rtos (/ (getvar "area") wa_ufa) 2 wa_pre) " M2. "))
		)
		((= pt "Dimscale")
			(setq dim (getint (strcat "\nDimscale: <" (rtos (getvar "dimscale")) "> ")))
			(if (= (type dim) 'INT) (setvar "dimscale" dim))
			(wrt)
		)
		((= pt "Precision")
			(setq pre (getint (strcat "\nPrecision: <" (rtos wa_pre) "> ")))
			(setq pre (if pre pre 1))
			(setq wa_pre pre)
			(wrt)
		)
		((= pt "Units")
			(cmd "'units")
		)
		((= pt "postFix")
			(princ )
			(princ )
			(setq psf (getstring (strcat "\nPostfix: <" wa_psf "> ")))
			(setq psf (if psf psf wa_psf))
			(if (= psf ".") (setq psf ""))
			(setq wa_psf psf)
			(wrt)
		)
		((listp pt)
			(setq a (strcat (rtos (/ (getvar "area") wa_ufa) 2 wa_pre) wa_psf))
			(entmake (list
				'(0 . "TEXT") (cons 1 a) (cons 8 txt_layer) (cons 10 pt)
				(cons 40 (* 3.0 wa_dfa (getvar "dimscale")))
			))
		)
	)
)

(defun c:wa (/ olderr a txt_layer insu)
	(setvar "cmdecho" 0)
	(command "_area" "0,0" "0,0" "")
	(setvar "cmdecho" 1)
	(command "_area")
	; 2025-11-26
	; 中望返回的不是 area 是 setvar
	; autocad 未测试
	(while (= (substr (getvar "cmdnames") 1 4) "AREA")
		(princ "\n")
		(princ (getvar "cmdnames"))
		(command pause)
	)
	(if (zerop (getvar "area")) nil (wrt))
	(princ)
)

(princ "loaded. Start as C:WA ")
(princ)
