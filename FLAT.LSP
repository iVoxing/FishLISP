(defun flt_lin (/ pt2)
	(setq 
		pt2 (cdr (assoc 11 ent))
		pt1 (list (car pt1) (cadr pt1) 0.0)
		pt2 (list (car pt2) (cadr pt2) 0.0)
		ent (subst (cons 10 pt1) (assoc 10 ent) ent)
		ent (subst (cons 11 pt2) (assoc 11 ent) ent)
	)
	(entmod ent)
)
 
(defun flt_els ()
	(setq pt1 (list (car pt1) (cadr pt1) 0.0))
	(entmod (subst (cons 10 pt1) (assoc 10 ent) ent))
)
 
(defun flt_ins (/ ssnn)
	(setq pt1 (list (car pt1) (cadr pt1) 0.0))
	(entmod (subst (cons 10 pt1) (assoc 10 ent) ent))
	(setq 
		ssnN (entnext ssn)
		ent (entget ssnn)
		typ (cdr (assoc 0 ent))
		pt1 (cdr (assoc 10 ent))
	)
	(while (/= typ "SEQEND")
		(if (= typ "ATTRIB")
			 (flt_lin)
			 (flt_els)
		)
		(setq 
			ssnn (entnext ssnn)
			ent (entget ssnn)
			typ (cdr (assoc 0 ent))
			pt1 (cdr (assoc 10 ent))
		)
	)
	(entupd ssn)
)

(defun c:flat (/ ss sslen count ssn ent pt1)
	(princ "\nSelect lines to flat:")
	(setq 
		ss (ssget)
		sslen (sslength ss)
		count 0
	)
	(princ "\nProcessing... ")
	(repeat sslen
		(setq 
			ssn (ssname ss count)
			ent (entget ssn)
			typ (cdr (assoc 0 ent))
			pt1 (cdr (assoc 10 ent))
			count (1+ count)
		)
		(if (or (= typ "LINE") (= typ "TEXT"))
			 (flt_lin)
			 (if (= typ "INSERT")
				(flt_ins)
				(flt_els)
			 )
	)
	)
	(princ "done!")
	(princ)
)
