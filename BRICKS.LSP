(foreach pat (list "t0510.pat" "t1010.pat" "t0520.pat")
	(if (findfile pat)
		nil
		(exit (strcat "\n填充文件 " pat "未找到"))
	)
)

(defun drw_brick (pat_ sc_ an_ / cl os hpt pt)
	(setq 
		cl (getvar "clayer")
		os (getvar "osmode")
	)
	(setvar "cmdecho" 0)
	(setvar "osmode" 0)
	(if (tblsearch "layer" "paint_t1")
		(setvar "clayer" "paint_t1")
		(cmd "_layer" "m" "paint_t1" "c" "33" "paint_t1" "")
	)
	(setvar "cmdecho" 1)
	(setvar "hpname" pat_)
	(setvar "hpang" (/ (* an_ pi) 180.0))
	(setvar "hpscale" sc_)
	(setq pt (getpoint "\nBase point: "))
	(if pt
		(progn
			(cmd "_ucs" "m" pt "")
			(command "_bhatch")
			(while (= (getvar "cmdnames") "BHATCH")
				(command pause)
			)
		)
	)
	(setvar "clayer" cl)
)

(defun c:bh () (drw_brick "t0520,o" 1 0) (princ))
(defun c:bv () (drw_brick "t0520,o" 1 90) (princ))
