; 选择一条Line，把一组和他相交的Line在交点打断
; F参数尚未提供给用户
; 不能处理Line以外的实体

(defun c:brk (/ en_l enm_l ent_l pt1 pt2 pt3 pt4 ss ssl idx int lay en ent ssl_m)
	(setvar "cmdecho" 0)
	(cmd "_undo" "g")
	(initget "Fence")
	(setq en_l (entsel "\nPick a line to edit: "))
	(cond 
		((= en_l "Fence")
			(setq pt1 (getpoint "\nStart point of fence line: "))
			(initget 32)
			(if pt1 (setq pt2 (getpoint pt1 "\nEnd point of fence line: ")))
		)
		((and (listp en_l) (setq ent_l (entget (setq enm_l (car en_l)))) (= (cdr (assoc 0 ent_l)) "LINE"))
			(setq pt1 (cdr (assoc 10 ent_l))
				pt2 (cdr (assoc 11 ent_l))
			)
	 	)
	)
	(if enm_l (entdel enm_l))
	(if pt2 (setq ss (ssget "f" (list pt1 pt2))))
	(if ss (setq ss (ssget "p" '((0 . "LINE")))))
	(if ss (setq ssl (sslength ss) idx 0))
	(if enm_l (entdel enm_l))
	(repeat ssl
		(setq 
			en (ssname ss idx)
			ent (entget en)
			pt3 (cdr (assoc 10 ent))
			pt4 (cdr (assoc 11 ent))
			int (inters pt1 pt2 pt3 pt4)
			lay (cdr (assoc 8 ent))
		)
		(if int (entmod (subst (cons 11 int) (assoc 11 ent) ent)) (setq ssl_m (1- ssl)))
		(if int (entmake (list '(0 . "LINE") (cons 8 lay) (cons 10 int) (cons 11 pt4))))
		(setq idx (1+ idx))
	)
	(cmd "_undo" "end")
	(setvar "cmdecho" 1)
	(princ (strcat "\n" (rtos (if ssl_m ssl_m ssl)) " line(s) broken."))
	(princ)
)
