(defun c:hc (/ cl)
	(setq cl (getvar "clayer"))
	(setvar "cmdecho" 0)
	(cmd "_layer" "make" "填充 30%" "C" "252" "" "")
	(if (setq ss (ssget (list (cons 8 FLLT_COL))))
		(cmd "_bhatch" "p" "solid" "s" ss "" "")
	)
	(setvar "clayer" cl)
	(setvar "cmdecho" 1)
	(princ)
)

(defun c:hs (/ cl)
	(setvar "cmdecho" 0)
	(if (setq ss (ssget))
		(cmd "_bhatch" "p" "solid" "s" ss "" "")
	)
	(setvar "cmdecho" 1)
	(princ)
)

(defun c:h31 (/ cl)
	(setq cl (getvar "clayer"))
	(setvar "cmdecho" 0)
	(cmd "_layer" "make" "面积" "C" "R" "" "")
	(if (setq ss (ssget))
		(cmd "_bhatch" "p" "ANSI31" "1000.0" "" "s" ss "" "")
	)
	(setvar "cmdecho" 1)
	(setvar "clayer" cl)
	(princ)
)

(princ "loaded. C:HC C:HS C:H31")
(princ)
