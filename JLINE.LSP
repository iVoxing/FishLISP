; 1997-12-18	Can edit in UCS now.
; 1996-07-22


(defun c:j (/ os oo cl ss ssl ucsf idx lay ent list_pt list_x list_y max_x min_x max_y min_y pt11 pt12 pt21 pt22 pt1 pt2)
	(princ "\nJoin lines to one. Start as C:J")
	(setq 
		os (getvar "osmode")
		oo (getvar "orthomode")
		ucsf (getvar "ucsfollow")
	)
	(setvar "osmode" 0)
	(setvar "orthomode" 0)
	(setvar "cmdecho" 0)
	(setvar "ucsfollow" 0)
	(cmd "_.ucs" "w")
	(setq cl (getvar "clayer"))
	(setq ss (ssget '((0 . "LINE"))))
	(setq ssl (sslength ss))
	(setq idx 0)
	(setq lay (cdr (assoc 8 (entget (ssname ss 0)))))
	(while (< idx ssl)
		(setq ent (entget (ssname ss idx)))
		(if (/= (cdr (assoc 8 ent)) lay)
			(exit (princ "The lines arn't on the same layer. "))
		)
		;; Get Endpoints and Xs, Ys
		(mapcar 
			'(lambda (code_)
				(setq 
					list_pt (append list_pt (list (cdr (assoc code_ ent))))
					list_x 	(append list_x (list (cadr (assoc code_ ent))))
					list_y 	(append list_y (list (caddr (assoc code_ ent))))
				)
			)
			'(10 11)
		)
		(setq idx (1+ idx))

	)
	(setq 
		max_x 	(apply 'max list_x)
		min_x 	(apply 'min list_x)
		max_y 	(apply 'max list_y)
		min_y 	(apply 'min list_y)
		z		(getvar "elevation")
		pt11 	(list max_x max_y z)
		pt12 	(list max_x min_y z)
		pt21 	(list min_x max_y z)
		pt22 	(list min_x min_y z)
	)
	(if (member pt11 list_pt)
		(if (member pt21 list_pt)
			(setq pt1 pt11 pt2 pt21)
			(setq pt1 pt11 pt2 pt22)
		)
		(if (member pt21 list_pt)
			(setq pt1 pt12 pt2 pt21)
			(setq pt1 pt12 pt2 pt22)
		)
	)
	(if (= max_x min_x) (setq pt1 pt11 pt2 pt12))
	(setvar "clayer" lay)
	(cmd "_erase" ss "" "line" pt1 pt2 "")
	(cmd "_.ucs" "p")
	(setvar "cmdecho" 1)
	(setvar "osmode" os)
	(setvar "orthomode" oo)
	(setvar "clayer" cl)
	(setvar "ucsfollow" ucsf)
	(princ)
)
