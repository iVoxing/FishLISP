(defun indim (/ sc cl bn loop) 
	(setq 
		sc   (getvar "dimscale")
		cl   (getvar "clayer")
		loop t
	)
	(setvar "cmdecho" 0)
	(setvar "clayer" "pdim")
	(while loop 
		(setq bn (getstring "\nBlock name:"))
		(if (or 
				(findfile (strcat bn ".dwg")) 
				(tblsearch "BLOCK" bn)
			)
			(setq loop nil)
			(princ "*Block not found*")
		)
	)
	(command-s "insert"  bn "x" sc "y" sc)
	(princ "\nInsert point:")
	(command pause)
	(princ "\nAngle:")
	(command pause)
	(setvar "cmdecho" 1)
	(setvar "clayer" cl)
	(princ)
)

(defun infur (/ cl bn loop) 
	(setq cl (getvar "clayer"))
	(setvar "cmdecho" 0)
	(setvar "clayer" "fur")
	(setq loop t)
	(while loop 
		(setq bn (getstring "\nBlock name:"))
		(if (or 
				(findfile (strcat bn ".dwg")) 
				(tblsearch "BLOCK" bn)
			)
			(setq loop nil)
			(princ "*Block not found*")
		)
	)
	(command-s "insert" bn "x" 1 "y" 1)
	(princ "\nInsert point:")
	(command pause)
	(princ "\nAngle:")
 	(command pause)
	(setvar "cmdecho" 1)
	(setvar "clayer" cl)
	(princ)
)

(princ "\nFishLISP Menu utilities loaded. ")
(princ)
