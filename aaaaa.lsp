(defun c:caaa(/ p)
	(setvar "CMDECHO" 0)
	(ca_draw_lines 60 4 0.25)
	(ca_draw_lines 60 4 -0.25)
	(princ)
)
(defun ca_draw_lines (len sep m / ca_i ca_x ca_lim)
	(setq ca_i -1)
	(setq ca_lim (/ len sep))
	(while (< ca_i ca_lim)
		(setq ca_x (+ m (* sep (1- ca_i))))
		;cmd"line" (list ca_x len) (list ca_x 0) "")
		(entmake (list '(0 . "LINE") (cons 10 (list ca_x len)) (cons 11 (list ca_x 0))))
		(setq ca_i (1+ ca_i))
	)
	ca_lim
)
